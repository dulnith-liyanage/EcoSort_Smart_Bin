"""Run this macro in FreeCAD to regenerate the assembly from the two print STLs.

The purchased hardware is represented by original simplified geometry, without
embedding third-party CAD. Units: mm. This is a static fit-test layout.
"""
from pathlib import Path
import json
import FreeCAD as App, FreeCADGui as Gui, Part, Mesh
from PySide import QtCore

root = Path(__file__).resolve().parent
doc = App.newDocument('EcoSort_Motor_Assembly')
V = App.Vector
objects = []

def box(x, y, z, p):
    return Part.makeBox(x, y, z, V(*p))

def add(name, shape, color=(0.2, 0.62, 0.66), note=''):
    assert not shape.isNull() and shape.isValid(), name
    obj = doc.addObject('Part::Feature', name)
    obj.Label = name.replace('_', ' ')
    obj.Shape = shape
    obj.addProperty('App::PropertyString', 'DesignNote')
    obj.DesignNote = note
    obj.ViewObject.ShapeColor = color
    obj.ViewObject.DisplayMode = 'Flat Lines'
    objects.append(obj)
    return obj

def stl_solid(filename):
    mesh = Mesh.Mesh(str(root / filename))
    shape = Part.Shape()
    shape.makeShapeFromMesh(mesh.Topology, 0.05)
    return Part.makeSolid(shape).removeSplitter()

mount = stl_solid('motor_mount_PRINT.stl')
mount.translate(V(0, 0, 260))
add('Original_motor_mount', mount, note='Exact original printed support geometry.')
for x in [-55, 55]:
    for y in [-40, 40]:
        shoe = stl_solid('rim_shoe_PRINT_FOUR.stl')
        if y < 0:
            shoe.rotate(V(), V(0, 0, 1), 180)
        shoe.translate(V(x, y, 234))
        add('Rim_shoe', shoe)

# Original envelope models: no manufacturer-specific detailed CAD or hole pattern.
# Body dimensions are nominal; ears/shaft are illustrative and require measurement.
servo = box(19.7, 40.7, 42.9, (-9.85, -20.35, 0))
servo = servo.fuse(box(19.7, 54, 3, (-9.85, -27, 28)))
servo = servo.fuse(Part.makeCylinder(3, 3, V(0, 10, 42.9)))
pan = servo.copy()
pan.translate(V(0, 0, 379))
add('Pan_servo_MG996R_APPROXIMATE', pan, (0.16, 0.18, 0.2),
    'Original simplified envelope. Shaft, ears and mounting holes are not fit references.')
tilt = servo.copy()
tilt.rotate(V(), V(0, 1, 0), 90)
tilt.translate(V(-22, 0, 448))
add('Tilt_servo_MG996R_APPROXIMATE', tilt, (0.16, 0.18, 0.2),
    'Original simplified envelope. Do not print this purchased component.')
carrier = box(60, 54, 3, (-30, -27, 424)).fuse(box(3, 54, 27, (-30, -27, 424)))
add('RB0051_pan_carrier_APPROXIMATE', carrier, (0.16, 0.18, 0.2),
    'Visual representation based on the user-identified Tronic RB0051 kit; dimensions unverified.')
upper = box(68, 60, 3, (-34, -30, 463))
for x in [-34, 31]:
    upper = upper.fuse(box(3, 60, 20, (x, -30, 443)))
    upper = upper.cut(Part.makeCylinder(3, 5, V(x-1, 0, 448), V(1, 0, 0)))
add('RB0051_tilting_U_bracket_APPROXIMATE', upper, (0.16, 0.18, 0.2))
tray = add('Existing_tray_APPROXIMATE', box(300, 220, 5, (-150, -110, 466)),
           (0.3, 0.6, 0.35), 'Placeholder for existing tray; attachment and clearance unverified.')
tray.ViewObject.Transparency = 60
assert len(objects) == 10
doc.recompute()
Part.export(objects, str(root / 'EcoSort_motor_assembly.step'))
doc.saveAs(str(root / 'EcoSort_motor_assembly.FCStd'))
(root / 'contents.json').write_text(json.dumps({
    'parts': [o.Name for o in objects],
    'geometry': 'Original support and shoes; original simplified purchased-hardware representations.',
    'third_party_cad_embedded': False,
}, indent=2) + '\n')
view = Gui.activeDocument().activeView()
view.setCameraOrientation((0.424708, 0.17592, 0.339852, 0.820473))
def finish():
    view.fitAll()
    Gui.updateGui()
    doc.save()
QtCore.QTimer.singleShot(1500, finish)
